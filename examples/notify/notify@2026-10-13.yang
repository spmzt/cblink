module notify {
  yang-version 1.1;
  namespace "urn:cblink:example:notify";
  prefix ntf;

  organization
    "cblink";
  contact
    "Pouria Mousavizadeh Tehrani <pouria@FreeBSD.org>";
  description
    "cblink's example of notifications: the server announces a tick
     to every subscriber of family 1's group 'notify'.";

  revision 2026-10-13 {
    description
      "Initial revision.";
  }

  notification tick {
    description
      "Time passed.";
    leaf seq {
      type uint64;
      description
        "The tick's number, from 1.";
    }
    leaf msec {
      type uint64;
      units "milliseconds";
      description
        "Milliseconds since the server started.";
    }
  }
}
