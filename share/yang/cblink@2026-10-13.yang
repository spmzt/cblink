module cblink {
  yang-version 1.1;
  namespace "urn:cblink:yang:cblink";
  prefix cbl;

  import ietf-yang-types {
    prefix yang;
    reference
      "RFC 6991: Common YANG Data Types";
  }
  import ietf-yang-structure-ext {
    prefix sx;
    reference
      "RFC 8791: YANG Data Structure Extensions";
  }

  organization
    "cblink";
  contact
    "Pouria Mousavizadeh Tehrani <pouria@FreeBSD.org>";
  description
    "The framework data of cblink's wire version 2.

     A version 2 body is one YANG-CBOR map (RFC 9254) whose top-level
     keys are absolute SIDs.  What version 1 carried under negative
     framework keys (CODE, MSG, PATH, COOKIE, MISS_TYPE, CREDIT) and in
     the control family's hello is defined here as YANG data structures
     (RFC 8791), so that a frame's framework items are typed and keyed
     by SID like any other data: an error, the credit of a stream, the
     limits exchanged at hello, the code and text of a stream's close,
     and the envelope of a notification.

     The frame header (24 bytes: magic, version, header length, length,
     family, command, flags, sequence number, stream id) is not YANG
     and is not modelled here.";

  revision 2026-10-13 {
    description
      "Initial revision.";
    reference
      "cblink docs/WIRE-FORMAT.md; Arcana docs/PLAN-SDN-YANG.md,
       'cblink 2: the protocol'.";
  }

  /*
   * Error tags
   */

  identity error-tag {
    description
      "The base of the error tags of RFC 6241, Appendix A.  Each
       names, in its reference, the HTTP status RFC 8040 maps it to,
       for a console that answers RESTCONF.";
    reference
      "RFC 6241: Network Configuration Protocol (NETCONF),
       Appendix A;
       RFC 8040: RESTCONF Protocol, Section 7";
  }

  identity in-use {
    base error-tag;
    description
      "The resource is in use.";
    reference
      "RFC 8040, Section 7: 409 Conflict";
  }

  identity invalid-value {
    base error-tag;
    description
      "A value in the request is not acceptable.";
    reference
      "RFC 8040, Section 7: 400 Bad Request, 404 Not Found or
       406 Not Acceptable";
  }

  identity too-big {
    base error-tag;
    description
      "The request or the reply is too large to handle
       (max-frame, max-depth or max-attrs).";
    reference
      "RFC 8040, Section 7: 413 Request Entity Too Large, or
       400 Bad Request for a reply";
  }

  identity missing-attribute {
    base error-tag;
    description
      "An expected attribute is missing.";
    reference
      "RFC 8040, Section 7: 400 Bad Request";
  }

  identity bad-attribute {
    base error-tag;
    description
      "An attribute value is not correct.";
    reference
      "RFC 8040, Section 7: 400 Bad Request";
  }

  identity unknown-attribute {
    base error-tag;
    description
      "An unexpected attribute is present.";
    reference
      "RFC 8040, Section 7: 400 Bad Request";
  }

  identity missing-element {
    base error-tag;
    description
      "An expected element is missing: version 1's MISS_TYPE.";
    reference
      "RFC 8040, Section 7: 400 Bad Request";
  }

  identity bad-element {
    base error-tag;
    description
      "An element value is not correct.";
    reference
      "RFC 8040, Section 7: 400 Bad Request";
  }

  identity unknown-element {
    base error-tag;
    description
      "An unexpected element is present: an unknown SID in an
       edit.";
    reference
      "RFC 8040, Section 7: 400 Bad Request";
  }

  identity unknown-namespace {
    base error-tag;
    description
      "An unexpected namespace is present: a SID of a module the
       receiver does not implement.";
    reference
      "RFC 8040, Section 7: 400 Bad Request";
  }

  identity access-denied {
    base error-tag;
    description
      "Access to the requested data or operation is denied.";
    reference
      "RFC 8040, Section 7: 401 Unauthorized or 403 Forbidden";
  }

  identity lock-denied {
    base error-tag;
    description
      "A lock is held by another connection.";
    reference
      "RFC 8040, Section 7: 409 Conflict";
  }

  identity resource-denied {
    base error-tag;
    description
      "The request could not be completed for lack of resources.";
    reference
      "RFC 8040, Section 7: 409 Conflict";
  }

  identity rollback-failed {
    base error-tag;
    description
      "A rollback was requested and failed.";
    reference
      "RFC 8040, Section 7: 500 Internal Server Error";
  }

  identity data-exists {
    base error-tag;
    description
      "The data to be created exists already.";
    reference
      "RFC 8040, Section 7: 409 Conflict";
  }

  identity data-missing {
    base error-tag;
    description
      "The data to be changed or deleted does not exist.";
    reference
      "RFC 8040, Section 7: 409 Conflict";
  }

  identity operation-not-supported {
    base error-tag;
    description
      "The operation is not supported by this implementation.";
    reference
      "RFC 8040, Section 7: 405 Method Not Allowed or
       501 Not Implemented";
  }

  identity operation-failed {
    base error-tag;
    description
      "The operation failed for a reason no other tag covers.";
    reference
      "RFC 8040, Section 7: 412 Precondition Failed or
       500 Internal Server Error";
  }

  identity partial-operation {
    base error-tag;
    status obsolete;
    description
      "Obsolete in RFC 6241; never sent.";
    reference
      "RFC 8040, Section 7: 500 Internal Server Error";
  }

  identity malformed-message {
    base error-tag;
    description
      "The frame was malformed: bad CBOR, or a body outside the
       strict profile.";
    reference
      "RFC 8040, Section 7: 400 Bad Request";
  }

  /*
   * Types
   */

  typedef errno {
    type uint32 {
      range "1..max";
    }
    description
      "An error number of FreeBSD's errno(2), kept beside the error
       tag for C programs and arcanactl.";
  }

  typedef text {
    type string {
      length "0..1024";
    }
    description
      "A human-readable message, at most CBL_ERRMSG_MAX characters.";
  }

  /*
   * Structures
   */

  sx:structure error {
    description
      "The body of an ERROR frame, or of an acknowledgement that
       carries a cookie: one error with the fields of RFC 8040's
       'errors' list entry, plus the errno and the cookie that
       version 1 sent under CODE and COOKIE.";
    reference
      "RFC 8040: RESTCONF Protocol, Section 8 (ietf-restconf,
       yang-errors)";
    leaf error-type {
      type enumeration {
        enum transport {
          description
            "The transport layer.";
        }
        enum rpc {
          description
            "The rpc or notification layer.";
        }
        enum protocol {
          description
            "The protocol operation layer.";
        }
        enum application {
          description
            "The server application layer.";
        }
      }
      mandatory true;
      description
        "The layer where the error occurred.";
    }
    leaf error-tag {
      type identityref {
        base error-tag;
      }
      mandatory true;
      description
        "The error tag.";
    }
    leaf error-app-tag {
      type string;
      description
        "The application-specific error tag.";
    }
    leaf error-path {
      type instance-identifier {
        require-instance false;
      }
      description
        "The node the error is about: version 1's PATH, in the same
         array shape on the wire (a SID, or a SID with keys).";
    }
    leaf error-message {
      type text;
      description
        "The message: version 1's MSG.";
    }
    anydata error-info {
      description
        "Further, error-specific data.";
    }
    leaf errno {
      type errno;
      description
        "The errno(2) value: version 1's CODE.";
    }
    leaf cookie {
      type binary {
        length "0..256";
      }
      description
        "Opaque data for the requester, as netlink's extended ack
         allows on success too: version 1's COOKIE.";
    }
  }

  sx:structure credit {
    description
      "The body of an S_CREDIT frame: more window for the sender of
       a stream.";
    reference
      "cblink docs/STREAMS.md, 'Flow control'";
    leaf increment {
      type uint32 {
        range "1..max";
      }
      units "octets";
      mandatory true;
      description
        "The bytes the receiver grants in addition to what is left:
         version 1's CREDIT.";
    }
  }

  sx:structure hello {
    description
      "The limits and the implementation each end announces when a
       connection starts, and the content-id of the YANG library it
       implements.";
    container limits {
      description
        "Receive limits of the announcing endpoint.";
      leaf max-frame {
        type uint64;
        units "octets";
        description
          "The largest frame accepted, header included.";
      }
      leaf max-depth {
        type uint32;
        description
          "The deepest nesting of a body accepted.";
      }
      leaf max-attrs {
        type uint32;
        description
          "The most values in one body accepted.";
      }
      leaf max-streams {
        type uint32;
        description
          "The most streams open at once.";
      }
      leaf stream-window {
        type uint32;
        units "octets";
        description
          "The default window of a stream.";
      }
    }
    leaf implementation {
      type string {
        length "1..63";
      }
      description
        "Implementation name and version.";
    }
    leaf content-id {
      type string;
      description
        "The content-id of the announcing end's YANG library, which
         changes when its modules, features or deviations do.";
      reference
        "RFC 8525: YANG Library, 'content-id'";
    }
  }

  sx:structure close {
    description
      "The body of an S_CLOSE or S_RESET frame: why a stream ends.";
    leaf code {
      type uint32;
      description
        "0 for a normal close, otherwise an errno(2) value.";
    }
    leaf message {
      type text;
      description
        "A human-readable reason.";
    }
  }

  sx:structure get {
    description
      "The parameters of a GET of family 1, 'cblink.yang': what to
       read, as CORECONF's FETCH names it.  Without it, or without a
       target, the whole datastore: every top-level data node the
       server has a handler for.";
    reference
      "draft-ietf-core-comi: CoAP Management Interface (CORECONF),
       Section 3.1.3";
    leaf-list target {
      type instance-identifier {
        require-instance false;
      }
      description
        "A node to read: its SID.  A list entry's, a SID with its
         keys, is for a later revision of the protocol.";
    }
    leaf xpath-filter {
      type string;
      description
        "An XPath expression over the nodes read (the targets, or the
         whole datastore), as NETCONF's xpath filter (RFC 6241,
         section 8.9): what it selects comes back, with the nodes above
         it and a list entry's keys, nothing else.  Its prefixes are
         its modules' names (XPath-lite, cblink's YANG.md).";
      reference
        "RFC 6241: Network Configuration Protocol (NETCONF), Section
         8.9";
    }
    leaf with-defaults {
      type enumeration {
        enum explicit {
          description
            "What the server has, as it has it: its basic mode.";
        }
        enum report-all {
          description
            "Every default in use too, a leaf the server has not set
             reported at its default.";
        }
        enum trim {
          description
            "A leaf at its default left out.";
        }
        enum report-all-tagged {
          description
            "As report-all, each leaf whose value is its default
             annotated so, ietf-defaults' 'default' true (the
             server's modules must have ietf-defaults).";
        }
      }
      description
        "How defaults are read (RFC 6243 section 3); without it,
         explicit.";
      reference
        "RFC 6243: With-defaults Capability for NETCONF, Section 3;
         draft-ietf-netconf-default-attribute: YANG Model for the
         NETCONF default attribute";
    }
    leaf with-origin {
      type empty;
      description
        "Of the operational datastore alone: each configuration node
         annotated with ietf-origin's 'origin' where it differs from
         its parent's (the server's modules must have ietf-origin):
         'intended' where running has the node (a leaf, with the same
         value), 'default' where it is a default in use, 'unknown'
         otherwise, a server telling not where else it came from.";
      reference
        "RFC 8342: Network Management Datastore Architecture (NMDA),
         Section 5.3.4; RFC 8527: RESTCONF Extensions to Support the
         NMDA, Section 3.2.2";
    }
  }

  sx:structure action {
    description
      "The node an RPC of family 1 invokes an action on, beside the
       action's input: the instance of the action's parent, a list
       entry with the keys of every list from the top down, as
       CORECONF's POST names the resource it acts on.";
    reference
      "draft-ietf-core-comi: CoAP Management Interface (CORECONF),
       Section 3.6; RFC 9254, Section 6.13.1";
    leaf target {
      type instance-identifier {
        require-instance false;
      }
      mandatory true;
      description
        "The action's parent: a container's SID, or a list entry's
         [SID, keys...].";
    }
  }

  sx:structure notification {
    description
      "The envelope of a NOTIFY frame: when the event happened, and
       the event itself, the data of a YANG notification.";
    reference
      "RFC 8040: RESTCONF Protocol, Section 6.4";
    leaf event-time {
      type yang:date-and-time;
      mandatory true;
      description
        "When the event happened.";
    }
    anydata event {
      description
        "The notification: one YANG notification of a module the
         sender implements, keyed by its SID.";
    }
  }

  sx:structure datastore {
    description
      "Beside a GET or an EDIT: the datastore it reads or changes (RFC
       8342).  Without it a GET reads the operational state and an EDIT
       changes running.";
    reference
      "RFC 8342: Network Management Datastore Architecture (NMDA)";
    leaf name {
      type enumeration {
        enum running {
          description
            "The configuration in use.";
        }
        enum candidate {
          description
            "A configuration being made, put in use by a commit (RFC
             6241 section 8.3).";
        }
        enum operational {
          description
            "The state in use, configuration and all.";
        }
      }
      mandatory true;
      description
        "The datastore.";
    }
  }

  sx:structure accept {
    description
      "Beside a request: the warnings it goes on despite, each by the
       error-app-tag the refusal that said it carried.";
    leaf-list warning {
      type string {
        length "1..64";
      }
      description
        "An error-app-tag.";
    }
  }

  sx:structure warnings {
    description
      "In an answer: what the request did that its sender should know,
       as RFC 6241's errors of severity warning.";
    reference
      "RFC 6241: Network Configuration Protocol (NETCONF), Section 4.3";
    list warning {
      description
        "A warning.";
      leaf error-path {
        type uint64;
        description
          "The SID of the node it is about; 0, none.";
      }
      leaf error-app-tag {
        type string;
        description
          "What it is, for a request to accept it by.";
      }
      leaf error-message {
        type string;
        description
          "What it says.";
      }
    }
  }

  sx:structure user {
    description
      "Beside a request: the user it is made for, RFC 8341's, which
       its access is checked as.  A peer that serves many users over
       one session (a console, a proxy) says whose request each one
       is; the receiver takes it only from a peer it trusts to say so.";
    reference
      "RFC 8341: Network Configuration Access Control Model,
       Section 2.2";
    leaf name {
      type string {
        length "1..253";
      }
      mandatory true;
      description
        "The user's name, as NACM's groups list it.";
    }
  }
}
