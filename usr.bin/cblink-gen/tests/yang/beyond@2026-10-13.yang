module beyond {
  yang-version 1.1;
  namespace "urn:cblink:yang:test:beyond";
  prefix b;

  revision 2026-10-13;

  list item {
    key "name";
    leaf name {
      type string;
    }
    leaf first {
      type boolean;
      must "position() = 1";
    }
  }
}
