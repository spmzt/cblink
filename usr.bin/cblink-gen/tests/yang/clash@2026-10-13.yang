module clash {
  yang-version 1.1;
  namespace "urn:cblink:yang:test:clash";
  prefix c;

  revision 2026-10-13;

  container top {
    leaf a-b {
      type string;
    }
    leaf a.b {
      type string;
    }
  }
}
