module example-last-modified {
  yang-version 1.1;
  namespace "urn:example:last-modified";
  prefix elm;

  import ietf-yang-types {
    prefix yang;
  }
  import ietf-yang-metadata {
    prefix md;
  }

  organization
    "cblink";
  contact
    "Pouria Mousavizadeh Tehrani <pouria@FreeBSD.org>";
  description
    "cblink's test of annotations: RFC 7952 section 2.1's example
     annotation, numbered as draft-ietf-core-yang-metadata's examples
     number it (61610).";

  revision 2026-10-14 {
    description
      "Initial revision.";
    reference
      "RFC 7952: Defining and Using Metadata with YANG, section 2.1";
  }

  md:annotation last-modified {
    type yang:date-and-time;
    description
      "This annotation contains the date and time when the
       annotated instance was last modified (or created).";
  }
}
