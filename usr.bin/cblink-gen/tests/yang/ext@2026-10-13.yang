module ext {
  yang-version 1.1;
  namespace "urn:cblink:yang:test:ext";
  prefix x;

  import ietf-yang-structure-ext {
    prefix sx;
  }
  import ietf-yang-schema-mount {
    prefix yangmnt;
  }

  revision 2026-10-13;

  sx:structure note {
    leaf text {
      type string;
    }
  }

  container root {
    yangmnt:mount-point "inner";
  }
}
