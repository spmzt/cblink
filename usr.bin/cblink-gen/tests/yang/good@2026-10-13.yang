module good {
  yang-version 1.1;
  namespace "urn:cblink:yang:test:good";
  prefix g;

  import ietf-yang-types {
    prefix yang;
  }

  revision 2026-10-13;

  feature extra;

  identity kind;

  identity extra-kind {
    if-feature extra;
    base kind;
  }

  container things {
    list thing {
      key "name";
      leaf name {
        type string {
          length "1..63";
        }
      }
      leaf seen {
        type yang:date-and-time;
      }
      leaf extra {
        if-feature extra;
        type identityref {
          base kind;
        }
      }
    }
  }
}
